RpkiSignedChecklist-2021
  { iso(1) member-body(2) us(840) rsadsi(113549)
    pkcs(1) pkcs9(9) smime(16) mod(0) }

DEFINITIONS EXPLICIT TAGS ::=
BEGIN
     -- This is a modified version of the ASN.1 module --
     -- from draft-ietf-sidrops-rpki-rsc-03#section-4  --

IMPORTS
  DigestAlgorithmIdentifier
  FROM CryptographicMessageSyntax2004
    { iso(1) member-body(2) us(840) rsadsi(113549) pkcs(1)
      pkcs-9(9) smime(16) modules(0) cms-2004(24) }

  ASIdOrRange, IPAddressOrRange
  FROM IPAddrAndASCertExtn -- in [RFC3779]
    { iso(1) identified-organization(3) dod(6) internet(1)
      security(5) mechanisms(5) pkix(7) mod(0)
      id-mod-ip-addr-and-as-ident(30) } ;

ct-rpkiSignedChecklist CONTENT-TYPE ::=
    { TYPE RpkiSignedChecklist IDENTIFIED BY
      id-ct-signedChecklist }

id-ct-signedChecklist OBJECT IDENTIFIER ::=
    { iso(1) member-body(2) us(840) rsadsi(113549) pkcs(1)
      pkcs-9(9) id-smime(16) id-ct(1) 48 }

RpkiSignedChecklist ::= SEQUENCE {
  version  [0]          INTEGER DEFAULT 0,
  resources             ResourceBlock,
  digestAlgorithm       DigestAlgorithmIdentifier,
  checkList             SEQUENCE SIZE (1..MAX) OF FileNameAndHash }

FileNameAndHash ::= SEQUENCE {
  fileName        IA5String OPTIONAL,
  hash            OCTET STRING }

ResourceBlock ::= SEQUENCE {
    asID         [0]       AsList OPTIONAL,
    ipAddrBlocks [1]       IPList OPTIONAL }
    -- at least one of asID or ipAddrBlocks MUST be present
    ( WITH COMPONENTS { ..., asID PRESENT} |
      WITH COMPONENTS { ..., ipAddrBlocks PRESENT } )

AsList ::= SEQUENCE (SIZE(1..MAX)) OF ASIdOrRange

IPList ::= SEQUENCE (SIZE(1..MAX)) OF IPAddressFamilyItem

IPAddressFamilyItem ::= SEQUENCE {    -- AFI &amp; optional SAFI --
   addressFamily        OCTET STRING (SIZE (2..3)),
   iPAddressOrRange     IPAddressOrRange }

END
