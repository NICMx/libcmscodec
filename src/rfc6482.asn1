RPKI-ROA { iso(1) member-body(2) us(840) rsadsi(113549)
	pkcs(1) pkcs9(9) smime(16) mod(0) 61 }

DEFINITIONS EXPLICIT TAGS ::= BEGIN
     -- This version of this ASN.1 module is a subset of   --
     -- the one defined in RFC 6482, appendix A.           --

IMPORTS

	IPAddress FROM IPAddrAndASCertExtn {
		iso(1) identified-organization(3) dod(6) internet(1) security(5)
		mechanisms(5) pkix(7) mod(0) id-mod-ip-addr-and-as-ident(30) };

RouteOriginAttestation ::= SEQUENCE {
	version [0] INTEGER DEFAULT 0,
	asID  ASID,
	ipAddrBlocks SEQUENCE (SIZE(1..MAX)) OF ROAIPAddressFamily }

ASID ::= INTEGER

ROAIPAddressFamily ::= SEQUENCE {
	addressFamily OCTET STRING (SIZE (2..3)),
	addresses SEQUENCE (SIZE (1..MAX)) OF ROAIPAddress }

ROAIPAddress ::= SEQUENCE {
	address IPAddress,
	maxLength INTEGER OPTIONAL }

END
