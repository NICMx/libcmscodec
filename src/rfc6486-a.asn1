RPKIManifest { iso(1) member-body(2) us(840) rsadsi(113549)
   pkcs(1) pkcs9(9) smime(16) mod(0) 60 }

DEFINITIONS EXPLICIT TAGS ::=

BEGIN
     -- This version of this ASN.1 module is a subset of   --
     -- the one defined in rfc6486#appendix-A.             --

-- EXPORTS ALL --

-- IMPORTS NOTHING --

-- Manifest Content Type: eContent

Manifest ::= SEQUENCE {
   version        [0] INTEGER DEFAULT 0,
   manifestNumber     INTEGER (0..MAX),
   thisUpdate         GeneralizedTime,
   nextUpdate         GeneralizedTime,
   fileHashAlg        OBJECT IDENTIFIER,
   fileList           SEQUENCE SIZE (0..MAX) OF FileAndHash
}

FileAndHash ::= SEQUENCE {
   file  IA5String,
   hash  BIT STRING
}

END
