SignedObjectSyntax
DEFINITIONS IMPLICIT TAGS ::=
BEGIN
     -- This version of this ASN.1 module is a subset of   --
     -- the one defined in rfc6488#section-2.1.6.4.4.      --

BinarySigningTime ::= BinaryTime

BinaryTime ::= INTEGER (0..MAX)

END
