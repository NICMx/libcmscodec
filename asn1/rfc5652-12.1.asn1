CryptographicMessageSyntax2004
  { iso(1) member-body(2) us(840) rsadsi(113549)
    pkcs(1) pkcs-9(9) smime(16) modules(0) cms-2004(24) }

DEFINITIONS IMPLICIT TAGS ::=
BEGIN
     -- This version of this ASN.1 module is a subset of   --
     -- the one defined in rfc5652#section-12.1.         --

-- EXPORTS All
-- The types and values defined in this module are exported for use
-- in the other ASN.1 modules.  Other applications may use them for
-- their own purposes.

IMPORTS

  -- Imports from RFC 5280 [PROFILE], Appendix A.1
        AlgorithmIdentifier, CertificateList,
        CertificateSerialNumber, Name, Time
           FROM PKIX1Explicit88
                { iso(1) identified-organization(3) dod(6)
                  internet(1) security(5) mechanisms(5) pkix(7)
                  mod(0) pkix1-explicit(18) };

-- Cryptographic Message Syntax

ContentInfo ::= SEQUENCE {
  contentType ContentType,
  content [0] EXPLICIT ANY DEFINED BY contentType }

ContentType ::= OBJECT IDENTIFIER

SignedData ::= SEQUENCE {
  version CMSVersion,
  digestAlgorithms DigestAlgorithmIdentifiers,
  encapContentInfo EncapsulatedContentInfo,
  certificates [0] IMPLICIT CertificateSet OPTIONAL,
  crls [1] IMPLICIT RevocationInfoChoices OPTIONAL,
  signerInfos SignerInfos }

DigestAlgorithmIdentifiers ::= SET OF DigestAlgorithmIdentifier

SignerInfos ::= SET OF SignerInfo

EncapsulatedContentInfo ::= SEQUENCE {
  eContentType ContentType,
  eContent [0] EXPLICIT OCTET STRING OPTIONAL }

-- Support 'Compatibility with PKCS #7' (section 5.2.1)
SignedDataPKCS7 ::= SEQUENCE {
  version CMSVersion,
  digestAlgorithms DigestAlgorithmIdentifiers,
  encapContentInfo EncapsulatedContentInfoPKCS7,
  certificates [0] IMPLICIT CertificateSet OPTIONAL,
  crls [1] IMPLICIT RevocationInfoChoices OPTIONAL,
  signerInfos SignerInfos }

EncapsulatedContentInfoPKCS7 ::= SEQUENCE {
  eContentType ContentType,
  eContent [0] EXPLICIT ANY DEFINED BY contentType OPTIONAL }

ContentTypePKCS7 ::= OCTET STRING

SignerInfo ::= SEQUENCE {
  version CMSVersion,
  sid SignerIdentifier,
  digestAlgorithm DigestAlgorithmIdentifier,
  signedAttrs [0] IMPLICIT SignedAttributes OPTIONAL,
  signatureAlgorithm SignatureAlgorithmIdentifier,
  signature SignatureValue,
  unsignedAttrs [1] IMPLICIT UnsignedAttributes OPTIONAL }

SignerIdentifier ::= CHOICE {
  issuerAndSerialNumber IssuerAndSerialNumber,
  subjectKeyIdentifier [0] CMSSubjectKeyIdentifier }

SignedAttributes ::= SET SIZE (1..MAX) OF CMSAttribute

UnsignedAttributes ::= SET SIZE (1..MAX) OF CMSAttribute

CMSAttribute ::= SEQUENCE {
  attrType OBJECT IDENTIFIER,
  attrValues SET OF CMSAttributeValue }

CMSAttributeValue ::= ANY

SignatureValue ::= OCTET STRING

CMSSubjectKeyIdentifier ::= OCTET STRING

DigestAlgorithmIdentifier ::= AlgorithmIdentifier

SignatureAlgorithmIdentifier ::= AlgorithmIdentifier

RevocationInfoChoices ::= SET OF RevocationInfoChoice

RevocationInfoChoice ::= CHOICE {
  crl CertificateList,
  other [1] IMPLICIT OtherRevocationInfoFormat }

OtherRevocationInfoFormat ::= SEQUENCE {
  otherRevInfoFormat OBJECT IDENTIFIER,
  otherRevInfo ANY DEFINED BY otherRevInfoFormat }

-- 2018-11-07: I changed this from "CertificateChoices" to "ANY,"
-- because asn1c should not actually parse the certificate.
-- That's libcrypto's job.
CertificateSet ::= SET OF ANY

IssuerAndSerialNumber ::= SEQUENCE {
  issuer Name,
  serialNumber CertificateSerialNumber }

CMSVersion ::= INTEGER  { v0(0), v1(1), v2(2), v3(3), v4(4), v5(5) }

-- The CMS Attributes

MessageDigest ::= OCTET STRING

SigningTime  ::= Time

Countersignature ::= SignerInfo

END -- of CryptographicMessageSyntax2004
